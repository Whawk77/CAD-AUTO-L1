;;; Read-only M4 visual-inspection snapshot extractor (DXF only; Core Console safe).

(defun m4-clean (value)
  (vl-string-translate (strcat (chr 9) (chr 13) (chr 10)) "   " (if value (vl-princ-to-string value) ""))
)

(defun m4-num (value)
  (if (numberp value) (rtos value 2 12) "")
)

(defun m4-row (stream fields / field line)
  (if fields
    (progn
      (setq line (m4-clean (car fields)))
      (foreach field (cdr fields) (setq line (strcat line (chr 9) (m4-clean field))))
      (write-line line stream)
    )
  )
)

(defun m4-error (stream scope handle failure)
  (m4-row stream (list "ERROR" scope handle (m4-clean failure)))
)

(defun m4-handle (entity / data)
  (if (and entity (setq data (entget entity))) (m4-clean (cdr (assoc 5 data))) "")
)

(defun m4-point-fields (point)
  (if (and point (listp point))
    (list (m4-num (car point)) (m4-num (cadr point)))
    (list "" "")
  )
)

(defun m4-point (x y) (list x y 0.0))

(defun m4-bounds-from-points (points / point minx miny maxx maxy)
  (if (null points)
    (list "" "" "" "")
    (progn
      (setq point (car points) minx (car point) maxx (car point) miny (cadr point) maxy (cadr point))
      (foreach point (cdr points)
        (setq minx (min minx (car point)) maxx (max maxx (car point))
              miny (min miny (cadr point)) maxy (max maxy (cadr point)))
      )
      (list (m4-num minx) (m4-num miny) (m4-num maxx) (m4-num maxy))
    )
  )
)

(defun m4-seg (stream handle index p1 p2)
  (m4-row stream (append (list "SEG" handle (itoa index)) (m4-point-fields p1) (m4-point-fields p2)))
)

(defun m4-angle-point (center radius angle)
  (m4-point (+ (car center) (* radius (cos angle))) (+ (cadr center) (* radius (sin angle))))
)

(defun m4-circle-source (stream handle data / center radius index count step p1 p2)
  (setq center (cdr (assoc 10 data)) radius (cdr (assoc 40 data)))
  (if (or (null center) (not (numberp radius)))
    (m4-error stream "source" handle "CIRCLE missing group 10 or 40")
    (progn
      (m4-row stream (append (list "SOURCE" handle "CIRCLE")
        (m4-bounds-from-points (list (m4-point (- (car center) radius) (- (cadr center) radius))
                                    (m4-point (+ (car center) radius) (+ (cadr center) radius))))))
      (setq index 0 count 64 step (/ (* 8.0 (atan 1.0)) count))
      (while (< index count)
        (setq p1 (m4-angle-point center radius (* index step))
              p2 (m4-angle-point center radius (* (1+ index) step)))
        (m4-seg stream handle (1+ index) p1 p2)
        (setq index (1+ index))
      )
    )
  )
)

(defun m4-arc-bounds-points (center radius start finish / points angle quarter)
  (setq points (list (m4-angle-point center radius start) (m4-angle-point center radius finish))
        quarter (/ (* 4.0 (atan 1.0)) 2.0)
        angle 0.0)
  (while (<= angle finish)
    (if (and (>= angle start) (<= angle finish)) (setq points (cons (m4-angle-point center radius angle) points)))
    (setq angle (+ angle quarter))
  )
  points
)

(defun m4-arc-source (stream handle data / center radius start finish two-pi index count step p1 p2)
  (setq center (cdr (assoc 10 data)) radius (cdr (assoc 40 data)) start (cdr (assoc 50 data)) finish (cdr (assoc 51 data))
        two-pi (* 8.0 (atan 1.0)))
  (if (or (null center) (not (numberp radius)) (not (numberp start)) (not (numberp finish)))
    (m4-error stream "source" handle "ARC missing group 10, 40, 50, or 51")
    (progn
      (if (< finish start) (setq finish (+ finish two-pi)))
      (m4-row stream (append (list "SOURCE" handle "ARC") (m4-bounds-from-points (m4-arc-bounds-points center radius start finish))))
      (setq index 0 count 32 step (/ (- finish start) count))
      (while (< index count)
        (setq p1 (m4-angle-point center radius (+ start (* index step)))
              p2 (m4-angle-point center radius (+ start (* (1+ index) step))))
        (m4-seg stream handle (1+ index) p1 p2)
        (setq index (1+ index))
      )
    )
  )
)

(defun m4-line-source (stream handle data / p1 p2)
  (setq p1 (cdr (assoc 10 data)) p2 (cdr (assoc 11 data)))
  (if (or (null p1) (null p2))
    (m4-error stream "source" handle "LINE missing group 10 or 11")
    (progn
      (m4-row stream (append (list "SOURCE" handle "LINE") (m4-bounds-from-points (list p1 p2))))
      (m4-seg stream handle 1 p1 p2)
    )
  )
)

(defun m4-insert-source (stream handle data / point sx sy p2)
  (setq point (cdr (assoc 10 data)) sx (abs (if (numberp (cdr (assoc 41 data))) (cdr (assoc 41 data)) 1.0))
        sy (abs (if (numberp (cdr (assoc 42 data))) (cdr (assoc 42 data)) sx)))
  (if point
    (progn
      (setq p2 (m4-point (+ (car point) sx) (+ (cadr point) sy)))
      (m4-row stream (append (list "SOURCE" handle "INSERT") (m4-bounds-from-points (list point p2))))
    )
    (m4-error stream "source" handle "INSERT missing group 10")
  )
)

(defun m4-source-entity-core (stream entity / data handle dxf)
  (setq data (entget entity) handle (m4-handle entity) dxf (m4-clean (cdr (assoc 0 data))))
  (cond
    ((= dxf "LINE") (m4-line-source stream handle data))
    ((= dxf "CIRCLE") (m4-circle-source stream handle data))
    ((= dxf "ARC") (m4-arc-source stream handle data))
    ((= dxf "INSERT") (m4-insert-source stream handle data))
    (T (m4-error stream "source" handle (strcat "unsupported DXF " dxf)))
  )
)

(defun m4-source-entity (stream entity / handle result)
  (setq handle (m4-handle entity) result (vl-catch-all-apply 'm4-source-entity-core (list stream entity)))
  (if (vl-catch-all-error-p result) (m4-error stream "source" handle (vl-catch-all-error-message result)))
)

(defun m4-find-char (text start code / index length)
  (setq index start length (strlen text))
  (while (and (<= index length) (/= (ascii (substr text index 1)) code)) (setq index (1+ index)))
  (if (<= index length) index nil)
)

(defun m4-stack-width (text text-height height-scale / index length start maximum width)
  (setq index 1 start 1 length (strlen text) maximum 0.0)
  (while (<= index length)
    (if (member (substr text index 1) '("^" "/" "#"))
      (progn
        (if (> index start)
          (setq width (m4-visible-width (substr text start (- index start)) (* text-height height-scale))
                maximum (max maximum width)))
        (setq start (1+ index))))
    (setq index (1+ index)))
  (if (> index start)
    (setq width (m4-visible-width (substr text start (- index start)) (* text-height height-scale))
          maximum (max maximum width)))
  maximum
)

(defun m4-visible-width (text text-height / base width scale current maximum index length char control terminator scale-text stacked)
  (setq base (* text-height 0.7) scale 1.0 current 0.0 maximum 0.0 index 1 length (strlen text))
  (while (<= index length)
    (setq char (substr text index 1))
    (cond
      ((and (= char "\\") (< index length))
        (setq control (strcase (substr text (1+ index) 1)))
        (cond
          ((and (= control "H") (setq terminator (m4-find-char text (+ index 2) 59)))
            (setq scale-text (vl-string-right-trim "xX" (substr text (+ index 2) (- terminator index 2))))
            (if (> (atof scale-text) 0.0) (setq scale (atof scale-text)))
            (setq index (1+ terminator)))
          ((= control "P")
            (setq maximum (max maximum current) current 0.0 index (+ index 2)))
          ((and (= control "S") (setq terminator (m4-find-char text (+ index 2) 59)))
            (setq stacked (m4-stack-width (substr text (+ index 2) (- terminator index 2)) text-height scale)
                  current (+ current stacked)
                  index (1+ terminator)))
          (T (setq index (1+ index)))))
      ((and (= char "%") (<= (+ index 2) length) (= (substr text (1+ index) 1) "%"))
        (setq current (+ current (* base scale)) index (+ index 3)))
      ((or (= char "{") (= char "}")) (setq index (1+ index)))
      (T (setq current (+ current (* base scale)) index (1+ index))))
  )
  (max (* base 2.0) maximum current)
)

(defun m4-text-value (data / dxf value chunks)
  (setq dxf (cdr (assoc 0 data)) value "")
  (if (= dxf "MTEXT")
    (progn
      (foreach pair data (if (= (car pair) 3) (setq chunks (cons (cdr pair) chunks))))
      (foreach chunk (reverse chunks) (setq value (strcat value chunk)))
    )
  )
  (if (cdr (assoc 1 data)) (setq value (strcat value (cdr (assoc 1 data)))))
  (m4-clean value)
)

(defun m4-text-bounds (data / point height width actual-width actual-height text visible-width rotation dxf attachment h-anchor v-anchor cosr sinr p1 p2 p3 p4)
  (setq point (cdr (assoc 10 data)) height (cdr (assoc 40 data)) text (m4-text-value data)
        actual-width (cdr (assoc 42 data)) actual-height (cdr (assoc 43 data)) dxf (cdr (assoc 0 data))
        attachment (cdr (assoc 71 data)) rotation (if (numberp (cdr (assoc 50 data))) (cdr (assoc 50 data)) 0.0))
  (if (or (null point) (not (numberp height)))
    nil
    (progn
      ;;; ponytail: width mirrors DimensionLayoutRules controls; use font metrics only if visual precision requires it.
      (setq visible-width (m4-visible-width text height)
            width (if (and (= dxf "MTEXT") (numberp actual-width) (> actual-width 0.0))
                    (min actual-width visible-width)
                    visible-width))
      (setq height (if (and (numberp actual-height) (> actual-height 0.0)) actual-height height)
            h-anchor (if (= dxf "MTEXT") (cond ((member attachment '(2 5 8)) 0.5) ((member attachment '(3 6 9)) 1.0) (T 0.0)) 0.0)
            v-anchor (if (= dxf "MTEXT") (cond ((member attachment '(1 2 3)) 1.0) ((member attachment '(4 5 6)) 0.5) (T 0.0)) 0.0)
            cosr (cos rotation) sinr (sin rotation)
            p1 (m4-point (+ (car point) (* (- h-anchor) width cosr) (* v-anchor height sinr))
                         (+ (cadr point) (* (- h-anchor) width sinr) (* (- v-anchor) height cosr)))
            p2 (m4-point (+ (car p1) (* width cosr)) (+ (cadr p1) (* width sinr)))
            p3 (m4-point (+ (car p1) (* height (- sinr))) (+ (cadr p1) (* height cosr)))
            p4 (m4-point (+ (car p2) (* height (- sinr))) (+ (cadr p2) (* height cosr))))
      (m4-bounds-from-points (list p1 p2 p3 p4))
    )
  )
)

(defun m4-annotation-layer (dimensions / data)
  (if (and dimensions (> (sslength dimensions) 0) (setq data (entget (ssname dimensions 0))))
    (m4-clean (cdr (assoc 8 data)))
    ""
  )
)

(defun m4-modelspace-text (stream annotation-layer / filter selection index count entity data dxf handle bounds)
  ;;; Test-only bridge: capture standalone annotation-layer text without changing product output.
  (setq filter (list (cons -4 "<OR") (cons 0 "TEXT") (cons 0 "MTEXT") (cons -4 "OR>") (cons 410 "Model")))
  (if (/= annotation-layer "") (setq filter (append filter (list (cons 8 annotation-layer)))))
  (setq selection (ssget "_X" filter)
        index 0 count (if selection (sslength selection) 0))
  (while (< index count)
    (setq entity (ssname selection index) data (entget entity) dxf (m4-clean (cdr (assoc 0 data))) handle (m4-handle entity)
          bounds (m4-text-bounds data))
    (if bounds
      (m4-row stream (append (list "TEXT" "MODELSPACE" handle) bounds))
      (m4-error stream "modelspace-text" handle (strcat dxf " missing group 10 or 40")))
    (setq index (1+ index))
  )
  count
)

(defun m4-solid-bounds (data / points point)
  (setq points '())
  (foreach code '(10 11 12 13)
    (if (setq point (cdr (assoc code data))) (setq points (cons point points)))
  )
  (if points (m4-bounds-from-points points) nil)
)

(defun m4-arrow-insert-bounds (data / point sx sy size p1 p2)
  (setq point (cdr (assoc 10 data)) size (getvar "DIMASZ")
        sx (if (and (numberp (cdr (assoc 41 data))) (> (abs (cdr (assoc 41 data))) 0.0)) (abs (cdr (assoc 41 data))) size)
        sy (if (and (numberp (cdr (assoc 42 data))) (> (abs (cdr (assoc 42 data))) 0.0)) (abs (cdr (assoc 42 data))) size))
  (if point
    (progn
      (setq p1 (m4-point (- (car point) sx) (- (cadr point) sy))
            p2 (m4-point (+ (car point) sx) (+ (cadr point) sy)))
      (m4-bounds-from-points (list p1 p2))
    )
    nil
  )
)

(defun m4-dimension-block (stream dimension-handle block-name / record entity data dxf component-handle bounds)
  (setq record (tblobjname "BLOCK" block-name))
  (if (null record)
    (m4-error stream "block" dimension-handle (strcat "missing block " block-name))
    (progn
      (setq entity (entnext record))
      (while (and entity (/= (cdr (assoc 0 (entget entity))) "ENDBLK"))
        (setq data (entget entity) dxf (m4-clean (cdr (assoc 0 data))) component-handle (m4-handle entity))
        (cond
          ((member dxf '("TEXT" "MTEXT"))
            (setq bounds (m4-text-bounds data))
            (if bounds (m4-row stream (append (list "TEXT" dimension-handle component-handle) bounds))
                       (m4-error stream "component" component-handle (strcat dxf " missing group 10 or 40"))))
          ((= dxf "SOLID")
            (setq bounds (m4-solid-bounds data))
            (if bounds (m4-row stream (append (list "ARROW" dimension-handle component-handle dxf) bounds))
                       (m4-error stream "component" component-handle "SOLID missing points")))
          ((= dxf "INSERT")
            (setq bounds (m4-arrow-insert-bounds data))
            (if bounds (m4-row stream (append (list "ARROW" dimension-handle component-handle dxf) bounds))
                       (m4-error stream "component" component-handle "INSERT missing group 10")))
        )
        (setq entity (entnext entity))
      )
    )
  )
)

(defun m4-dimension-core (stream entity / data handle measurement ext1 ext2 defpoint textpoint block)
  (setq data (entget entity) handle (m4-handle entity) measurement (cdr (assoc 42 data))
        ext1 (cdr (assoc 13 data)) ext2 (cdr (assoc 14 data)) defpoint (cdr (assoc 10 data))
        textpoint (cdr (assoc 11 data)) block (m4-clean (cdr (assoc 2 data))))
  (m4-row stream (append (list "DIM" handle (m4-num measurement))
    (m4-point-fields ext1) (m4-point-fields ext2) (m4-point-fields defpoint) (m4-point-fields textpoint)
    (list block (m4-num (cdr (assoc 50 data))))))
  (if (/= block "") (m4-dimension-block stream handle block))
)

(defun m4-dimension (stream entity / handle result)
  (setq handle (m4-handle entity) result (vl-catch-all-apply 'm4-dimension-core (list stream entity)))
  (if (vl-catch-all-error-p result) (m4-error stream "dimension" handle (vl-catch-all-error-message result)))
)

(defun m4-selection-count (selection)
  (cond ((= (type selection) 'PICKSET) (sslength selection)) ((listp selection) (length selection)) (T 0))
)

(defun m4-each-source (stream selection / index count entity)
  (cond
    ((= (type selection) 'PICKSET)
      (setq index 0 count (sslength selection))
      (while (< index count) (setq entity (ssname selection index)) (if entity (m4-source-entity stream entity)) (setq index (1+ index))))
    ((listp selection) (foreach entity selection (if entity (m4-source-entity stream entity))))
  )
)

(defun m4-text-font (/ style)
  (setq style (tblsearch "STYLE" (getvar "TEXTSTYLE")))
  (if style (m4-clean (cdr (assoc 3 style))) "")
)

(defun m4-capture-core (stream source-selection case-id expected-direction include-modelspace-text / dimensions index count annotation-layer modelspace-text-count)
  (m4-row stream (list "META" "schemaVersion" "1"))
  (m4-row stream (list "META" "caseId" case-id))
  (m4-row stream (list "META" "expectedDirection" expected-direction))
  (m4-row stream (list "META" "sourceCount" (itoa (m4-selection-count source-selection))))
  (m4-row stream (list "ENV" "ACADVER" (getvar "ACADVER")))
  (m4-row stream (list "ENV" "DWGNAME" (getvar "DWGNAME")))
  (m4-row stream (list "ENV" "DWGPREFIX" (getvar "DWGPREFIX")))
  (m4-row stream (list "ENV" "DIMSTYLE" (getvar "DIMSTYLE")))
  (m4-row stream (list "ENV" "DIMSCALE" (m4-num (getvar "DIMSCALE"))))
  (m4-row stream (list "ENV" "DIMTXT" (m4-num (getvar "DIMTXT"))))
  (m4-row stream (list "ENV" "DIMASZ" (m4-num (getvar "DIMASZ"))))
  (m4-row stream (list "ENV" "TEXTSTYLE" (getvar "TEXTSTYLE")))
  (m4-row stream (list "ENV" "TEXTFONT" (m4-text-font)))
  (m4-each-source stream source-selection)
  (setq dimensions (ssget "_X" '((0 . "DIMENSION") (410 . "Model"))))
  (setq count (if dimensions (sslength dimensions) 0))
  (m4-row stream (list "META" "dimensionCount" (itoa count)))
  (setq index 0)
  (while (< index count) (m4-dimension stream (ssname dimensions index)) (setq index (1+ index)))
  (setq annotation-layer (m4-annotation-layer dimensions))
  (m4-row stream (list "META" "annotationLayer" annotation-layer))
  (setq modelspace-text-count (if include-modelspace-text (m4-modelspace-text stream annotation-layer) 0))
  (m4-row stream (list "META" "modelspaceTextCount" (itoa modelspace-text-count)))
)

(defun m4-capture-run (sourceSelection snapshotPath caseId expectedDirection include-modelspace-text / stream result)
  (setq stream (open snapshotPath "w"))
  (if stream
    (progn
      (setq result (vl-catch-all-apply 'm4-capture-core (list stream sourceSelection caseId expectedDirection include-modelspace-text)))
      (if (vl-catch-all-error-p result) (m4-error stream "top" "" (vl-catch-all-error-message result)))
      (close stream)
      (not (vl-catch-all-error-p result))
    )
    nil
  )
)

(defun m4-capture (sourceSelection snapshotPath caseId expectedDirection)
  (m4-capture-run sourceSelection snapshotPath caseId expectedDirection nil)
)

(defun m4-capture-modelspace (sourceSelection snapshotPath caseId expectedDirection)
  ;;; Test-only entry point; normal Core/nightly capture remains dimension-owned.
  (m4-capture-run sourceSelection snapshotPath caseId expectedDirection T)
)

(princ)
